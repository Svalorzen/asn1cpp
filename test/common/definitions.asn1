TEST DEFINITIONS AUTOMATIC TAGS ::= BEGIN

    TestInteger ::= SEQUENCE
    {
        integer             INTEGER
    }

    TestBoolean ::= SEQUENCE
    {
        boolean             BOOLEAN
    }

    TestPrintableString ::= SEQUENCE
    {
        string              PrintableString
    }

    TestEnumType ::= ENUMERATED
    {
        value0              (0),
        value1              (1),
        value2              (2)
    }

    TestEnum ::= SEQUENCE
    {
        enm                 TestEnumType
    }

    TestNested ::= SEQUENCE
    {
        nested              TestInteger
    }

    TestOptional ::= SEQUENCE
    {
        integer             INTEGER OPTIONAL,
        string              PrintableString OPTIONAL,
        boolean             BOOLEAN OPTIONAL,
        sequence            SEQUENCE OF INTEGER OPTIONAL,
        nested              SEQUENCE OF TestInteger OPTIONAL
    }

    TestSequenceOf ::= SEQUENCE
    {
        integer             SEQUENCE OF INTEGER,
        string              SEQUENCE OF PrintableString,
        boolean             SEQUENCE OF BOOLEAN,
        nested              SET OF TestInteger
    }

    -- Unfortunately even if SEQUENCE OF depends on the SET OF code, we have an
    -- inverse dependency since the asn1 compiler does not produce the
    -- SET_OF_encode_uper function, and we use the SEQUENCE OF one to fix this
    -- and allow compilation of the generated sources.
    TestSetOf ::= SEQUENCE
    {
        integer             SET OF INTEGER,
        string              SET OF PrintableString,
        boolean             SET OF BOOLEAN,
        nested              SET OF TestInteger
    }

END
